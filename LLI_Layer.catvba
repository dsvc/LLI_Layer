Attribute VB_Name = "Main_LLI_Layer"
Option Explicit

Public Type iRGB
 R As Long
 G As Long
 b As Long
End Type

Public Type iVisuProp
 LT As Long
 LS As Long
 Col As Long
 FontS As Long
End Type

Public ATable_LS(50)
Public ATable_LT(50)
Public ATable_L(50)
Public ATable_Color(50)
Public ATable_Text(50)

Dim version, macroname, Language

Sub CATMain()

Language = "VBA"
version = "1.2"
macroname = "LLI_Layer"
'###################################################################
'#####
'#####
'###      Catia V5 R21
'###
'###      Based on the geometry of a Layer definition is CATDrawing
'####     assigned lines of type, color and line thickness
'#####
'#####
'#####    Thomas Wassel
'#####    cenit AG
'#####    Lyoner Str. 20
'#####    D-60528 Frankfurt / M.
'#####    t.wassel@ cenit.de
'#####
'###################################################################
'#####
'#####    01.09.13    2D Text Color,Dimension Color and Font Size is adjusted using Layer definition.
'#####    04.9.13     2D ThreadLine, AxisLine; CenterLine
'#####    12.9.13     Global Declaration of the Excel variables
'#####    20.9.13     Binding " Option Explict"
'#####    30.9.13     CATIA.DisplayFileAlerts = True

'***Fehlerbehandlung einschalten
   On Error Resume Next
    
    CATIA.DisplayFileAlerts = True
              
             Dim activedoc As Document
             Set activedoc = CATIA.ActiveDocument
             If Err.Number <> 0 Then
                MsgBox "Es ist kein Dokument geöffnet", vbOKOnly, macroname + " " + version + " **CENIT AG**"
                Exit Sub
            End If
              
              'Dokumentart
            If (Right(activedoc.Name, 10) <> "CATDrawing") Then
                MsgBox "Aktives Dokument ist kein CATDrawing !", vbOKOnly, macroname + " " + version + " **CENIT AG**"
               Exit Sub
            End If

Dim Q As New clsGVI
Dim sStr As String
Dim i As Integer
Dim linetype
Dim width
width = CLng(0)
linetype = CLng(0)

CATIA.Application.StatusBar = macroname + "   " + version + "in Work"
Q.StartExcel
Q.Excel_Close

For i = 1 To UBound(ATable_L)
    If ATable_L(i) = 0 Then
    Exit For
    Else
    Q.selectLayer (i)
    Q.GeomProp (i)
    Q.selectText (i)
    'Q.selectCase (i)  '// Option without Excel
    Q.TextProp (i)
    Q.selectDim (i)
    Q.DimProp (i)
    End If
       
Next

CATIA.Application.StatusBar = macroname + "  " + version + "  " + "finished"

If Err.Number <> 0 Then
    Err.Description = "Error Code"
    Q.AppErr
    Exit Sub
    End If
End Sub
'###### End Main Methode #####################################

Attribute VB_Name = "clsGVI"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
'Global Declarieren
Public xlsAppl As Object
Public xlsWbk As Object
Public xlsWks As Object
Public xlsApplWarBereitsOffen As Boolean


'###### Start Geometry Search and Selection ########################

Public Function selectLayer(ByVal L As Integer)

'***Fehlerbehandlung einschalten
On Error Resume Next

Dim str, strD1, strD2, strD3, strD4, strD5, strD6, strD7, strD8, strD9, strD10, strD11 As String
Dim strE1, strE2, strE3, strE4, strE5, strE6, strE7, strE8, strE9, strE10, strE11 As String


selectLayer = L
str = L
strD1 = "Drafting.Linie.Layer=" & str
strD2 = "Drafting.Generiertes Element.Layer=" & str
strD3 = "Drafting.Kreis.Layer=" & str
strD4 = "Drafting.Polylinie.Layer=" & str
strD5 = "Drafting.Text.Layer=" & str
strD6 = "Drafting.Bemaßung.Layer=" & str
strD7 = "Drafting.Gewinde.Layer=" & str
strD8 = "Drafting.Achslinie.Layer=" & str
strD9 = "Drafting.Mittellinie.Layer=" & str
strD10 = "Drafting.Punkt.Layer=" & str
strD11 = strD1 + "+" + strD2 + "+" + strD3 + "+" + strD4 + "+" + strD5 + "+" + strD6 + "+" + strD7 + "+" + strD8 + "+" + strD9 + "+" + strD10


strE1 = "Drafting.Line.Layer=" & str
strE2 = "Drafting.Generated Item.Layer=" & str
strE3 = "Drafting.Circle.Layer=" & str
strE4 = "Drafting.Polyline.Layer=" & str
strE5 = "Drafting.Text.Layer=" & str
strE6 = "Drafting.Dimension.Layer=" & str
strE7 = "Drafting.Thread.Layer=" & str
strE8 = "Drafting.'Axis Line'.Layer=" & str
strE9 = "Drafting.'Center Line'.Layer=" & str
strE10 = "Drafting.Point.Layer=" & str
strE11 = strE1 + "+" + strE2 + "+" + strE3 + "+" + strE4 + "+" + strE5 + "+" + strE6 + "+" + strE7 + "+" + strE8 + "+" + strE9 + "+" + strE10

 
Dim i As Integer
Dim drwDoc As Document
Dim drwText As DrawingText
Set drwDoc = CATIA.ActiveDocument
Set selectLayer = drwDoc.Selection

'#### suche in englisch
selectLayer.Search strE11

If Err.Number <> 0 Then

'#### suche in deutsch
selectLayer.Search strD11

End If

selectLayer.Remove (i)

End Function
'###### End Geometry Search and Selection ########################

'###### Start Text Search and Selection ########################

Public Function selectText(ByVal L As Integer)

'***Fehlerbehandlung einschalten
On Error Resume Next

Dim str, strD1, strD2, strD3, strD4, strD5, strD6 As String
Dim strE1, strE2, strE3, strE4, strE5, strE6 As String


selectText = L
str = L

strE1 = "Drafting.Text.Layer=" & str
  
Dim i As Integer
Dim drwDoc As Document
Dim drwText As DrawingText
Set drwDoc = CATIA.ActiveDocument
Set selectText = CATIA.ActiveDocument.Selection

'#### suche in englisch
selectText.Search strE1

If Err.Number <> 0 Then

AppErr

End If

selectText.Remove (i)

End Function
'###### End Text Search and Selection ########################

'###### Start Dimension Search and Selection ########################

Public Function selectDim(ByVal L As Integer)

'***Fehlerbehandlung einschalten
On Error Resume Next

Dim str, strD1, strD2, strD3, strD4, strD5, strD6 As String
Dim strE1, strE2, strE3, strE4, strE5, strE6 As String

selectDim = L
str = L

strE1 = "Drafting.Dimension.Layer=" & str

strD1 = "Drafting.Bemaßung.Layer=" & str

 
Dim i As Integer
Dim drwDoc As Document
Dim drwText As DrawingText
Set drwDoc = CATIA.ActiveDocument
Set selectDim = CATIA.ActiveDocument.Selection

'#### suche in englisch
selectDim.Search strE1

If Err.Number <> 0 Then

'#### suche in deutsch
selectDim.Search strD1

End If


selectDim.Remove (i)

End Function
'###### End Dimension Search and Selection ########################

'###### VisProperties_ 2D Geometrie ########################

Public Function GeomProp(ByVal L As Integer)

'***Fehlerbehandlung einschalten
On Error Resume Next

Dim colorArray As Variant
Dim f As Integer
Dim visProp As VisPropertySet
Dim Element As GeometricElements
Dim layer As Long
Dim layertype As CatVisLayerType


Set visProp = CATIA.ActiveDocument.Selection.VisProperties
layer = CLng(0)
visProp.GetLayer layertype, layer
f = L
            
colorArray = Split(ATable_Color(f), ",", -1, 1)

visProp.SetRealColor colorArray(0), colorArray(1), colorArray(2), 1
visProp.SetRealLineType ATable_LT(f), 1
visProp.SetRealWidth ATable_LS(f), 1

End Function
'###### End VisProperties_ 2D Geometrie ########################

'###### TextProperties_ 2D Geometrie ########################

Public Function TextProp(ByVal L As Integer)

'***Fehlerbehandlung einschalten
On Error Resume Next

Dim iStart, iLen As Long
Dim i, f As Integer
Dim drwDoc As Document
Dim drwText As DrawingText
Set drwDoc = CATIA.ActiveDocument
Set TextProp = drwDoc.Selection

f = L

For i = 1 To TextProp.Count

Set drwText = TextProp.Item(i).Value
drwText.SetFontSize iStart, iLen, ATable_Text(f)
'drwText.SetFontName 0, 0, "Arial (TrueType)"    ###### Option FontName ###########
'drwText.TextProperties.Update
'TextProp.Remove (i)
Next

TextProp.Clear

End Function
'###### End Text Properties_ 2D Geometrie ########################

'###### Dimension Properties_ 2D Geometrie ########################

Public Function DimProp(ByVal L As Integer)

'***Fehlerbehandlung einschalten
On Error Resume Next
Dim iStart, iLen As Long
Dim b As Boolean
Dim i, f As Integer
Dim drwDoc As Document
Dim drwDim As DrawingText
Set drwDoc = CATIA.ActiveDocument
Set DimProp = drwDoc.Selection

f = L

For i = 1 To DimProp.Count

Set drwDim = DimProp.Item(i).Value
drwDim.SetFontSize iStart, iLen, ATable_Text(f)

Next

DimProp.Clear

End Function
'###### End Dimension Properties_ 2D Geometrie ########################

'######Dressup definition layer, line type, line thickness ###########

Public Function selectCase(ByVal L As Integer)

'***Fehlerbehandlung einschalten
On Error Resume Next

Dim Element As GeometricElements
Dim layer
Dim layertype As CatVisLayerType
        
Set visProp = CATIA.ActiveDocument.Selection.VisProperties
layer = CLng(0)
visProp.GetLayer layertype, layer


'###### Option without Excel Sheet ###########

    Select Case L

    Case "0"  '### Layer 0 ###
        visProp.SetRealColor 0, 255, 255, 1
        visProp.SetRealLineType 1, 1
        visProp.SetRealWidth 1, 1
    Case "1"
        visProp.SetRealColor 0, 255, 255, 1
        visProp.SetRealLineType 1, 1
        visProp.SetRealWidth 1, 1
    Case "2"
        visProp.SetRealColor 0, 0, 0, 1
        visProp.SetRealLineType 1, 1
        visProp.SetRealWidth 1, 1
    Case "3"
        visProp.SetRealColor 255, 0, 0, 1
        visProp.SetRealLineType 1, 1
        visProp.SetRealWidth 1, 1
    Case "4"
        visProp.SetRealColor 255, 255, 0, 1
        visProp.SetRealLineType 4, 4
        visProp.SetRealWidth 1, 1
    Case "5"
        visProp.SetRealColor 0, 0, 0, 1
        visProp.SetRealLineType 1, 1
        visProp.SetRealWidth 1, 1
    Case "6"
        visProp.SetRealColor 0, 0, 255, 1
        visProp.SetRealLineType 1, 1
        visProp.SetRealWidth 1, 1
    Case "11"
        visProp.SetRealColor 0, 255, 255, 1
        visProp.SetRealLineType 1, 1
        visProp.SetRealWidth 1, 1
    Case "12"
        visProp.SetRealColor 0, 0, 0, 1
        visProp.SetRealLineType 1, 1
        visProp.SetRealWidth 1, 1
    Case "13"
        visProp.SetRealColor 255, 0, 0, 1
        visProp.SetRealLineType 1, 1
        visProp.SetRealWidth 1, 1
    Case "14"
        visProp.SetRealColor 255, 255, 0, 1
        visProp.SetRealLineType 1, 1
        visProp.SetRealWidth 1, 1
    Case "16"
        visProp.SetRealColor 0, 0, 255, 1
        visProp.SetRealLineType 1, 1
        visProp.SetRealWidth 1, 1

    End Select

'######Dressup definition layer, line type, line thickness ###########


End Function

Sub StartExcel()

'Locale Declaration
'Dim xlsAppl As Excel.Application
'Dim xlsWbk As Excel.Workbook

On Error Resume Next
       
Dim visProp As Object
Dim strPath$
Dim strXlsFile$
Dim WbkOffen As Boolean
Dim bolGleichnamigeWbkOffen As Boolean
Dim i, e, f As Integer
Dim A, b, C As Long
Dim G As Double
Dim D As String
Dim str As String
Dim strA, strB, strC, strD, strG As String
Dim strGA, strGB, strGC, strGD, strGG As String

Dim Value As String
Dim bolXlsApplLiefNicht, bolWbkOffen As Boolean
Dim Element As GeometricElements
Dim layer
Dim colorArray
Dim layertype As CatVisLayerType
Set visProp = CATIA.ActiveDocument.Selection.VisProperties
layer = CLng(0)
visProp.GetLayer layertype, layer

strA = "A"
strB = "B"
strC = "C"
strD = "D"
strG = "E"
e = 1
i = 2

Value = CATIA.SystemService.Environ("CATIATMP")
strXlsFile$ = "LLI_Layer.xlsx"
strPath$ = Value

    On Error Resume Next
    Set xlsAppl = GetObject(, "Excel.Application")
    If Err.Number <> 0 Then bolXlsApplLiefNicht = True
    Err.Clear
        
    On Error GoTo ErrHandler
    
    If xlsAppl Is Nothing Then
    Set xlsAppl = CreateObject("Excel.Application")
    End If
    
    xlsAppl.Visible = False
    
 
 bolWbkOffen = False
 bolGleichnamigeWbkOffen = False
 For Each xlsWbk In xlsAppl.Workbooks
  If UCase(xlsWbk.Name) = UCase(strXlsFile$) Then
   bolGleichnamigeWbkOffen = True
   If UCase(xlsWbk.Path) = UCase(strPath$) Then
    bolWbkOffen = True
    Exit For
   End If
  End If
 Next
 
 If bolGleichnamigeWbkOffen And Not bolWbkOffen Then
  'MsgBox "Gleichnamige " & strXlsFile$ & " bereits geöffnet"
 Exit Sub
 End If
 
 xlsAppl.EnableEvents = False
 
 If Not bolWbkOffen And Not bolGleichnamigeWbkOffen Then
   Set xlsWbk = xlsAppl.Workbooks.Open(Filename:=strPath$ & "\" & strXlsFile)
 End If
 

For i = 2 To 50
    
    str = i
    strGA = strA + str
    A = xlsWbk.Worksheets("Tabelle1").Range(strGA).Value
    ATable_LS(e) = A
    strGB = strB + str
    b = xlsWbk.Worksheets("Tabelle1").Range(strGB).Value
    ATable_LT(e) = b
    strGC = strC + str
    C = xlsWbk.Worksheets("Tabelle1").Range(strGC).Value
    ATable_L(e) = C
    strGD = strD + str
    D = xlsWbk.Worksheets("Tabelle1").Range(strGD).Value
    ATable_Color(e) = D
    strGG = strG + str
    G = xlsWbk.Worksheets("Tabelle1").Range(strGG).Value
    ATable_Text(e) = G
    e = e + 1

Next


Exit Sub

'###### Error Handling ########################
ErrHandler:
 MsgBox Err.Description, vbCritical, Err.Number
 Set xlsWbk = Nothing
 xlsAppl.DisplayAlerts = True
 xlsAppl.Visible = True
 Set xlsAppl = Nothing
  
End Sub

Sub Excel_Close()

Dim xlsWb As Object

On Error Resume Next

Set xlsWb = Nothing
If xlsApplWarBereitsOffen Then
 xlsAppl.Visible = False
 xlsAppl.DisplayAlerts = True
 Set xlsAppl = Nothing
Else
  For Each xlsWb In xlsAppl.Workbooks
  xlsWb.Close SaveChanges:=False
 Next
 Set xlsWb = Nothing
 xlsAppl.DisplayAlerts = True
 xlsAppl.Quit
 Set xlsAppl = Nothing
End If

End Sub

'###### Error Handling ########################



Public Function AppErr()

    MsgBox "Fehler:" + Chr(10) + Chr(10) + _
                   "Fehlernummer:" + Chr(9) + CStr(Err.Number) + Chr(10) + _
                   "Fehlerquelle:" + Chr(9) + CStr(Err.Source) + Chr(10) + _
                   "Beschreibung:" + Chr(9) + CStr(Err.Description), vbOKOnly, macroname + " " + version + "**CENIT AG**"

End Function
'###### Error Handling ########################
